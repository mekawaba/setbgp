module setbgp {

  namespace "http://example.com/setbgp";
  prefix setbgp;

  import ietf-inet-types {
    prefix inet;
  }
  import tailf-common {
    prefix tailf;
  }
  import tailf-ncs {
    prefix ncs;
  }

  description
    "Bla bla...";

  revision 2016-01-01 {
    description
      "Initial revision.";
  }

  list setbgp {
    description "This is an RFS skeleton service";

    key name;
    leaf name {
      tailf:info "Unique service id";
      tailf:cli-allow-range;
      type string;
    }

    uses ncs:service-data;
    ncs:servicepoint setbgp-servicepoint;

    // may replace this with other ways of refering to the devices.
    leaf dev1 {
      type leafref {
        path "/ncs:devices/ncs:device/ncs:name";
      }
    }
    leaf dev2 {
      type leafref {
        path "/ncs:devices/ncs:device/ncs:name";
      }
    }

    // replace with your own stuff here
    leaf dev1-loop {
      type inet:ipv4-address;
    }
    leaf dev2-loop {
      type inet:ipv4-address;
    }
    leaf as {
      type uint16{
        range "100..300"{
          error-message "AS number must be within 100 to 300";
              }
    }
    }
  }
}
